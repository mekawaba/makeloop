module makeloop {

  namespace "http://example.com/makeloop";
  prefix makeloop;

  import ietf-inet-types {
    prefix inet;
  }
  import tailf-common {
    prefix tailf;
  }
  import tailf-ncs {
    prefix ncs;
  }

  description
    "Bla bla...";

  revision 2016-01-01 {
    description
      "Initial revision.";
  }

  list makeloop {
    description "This is an RFS skeleton service";

    key name;
    leaf name {
      tailf:info "Unique service id";
      tailf:cli-allow-range;
      type string;
    }

    uses ncs:service-data;
    ncs:servicepoint makeloop-servicepoint;

    // may replace this with other ways of refering to the devices.
    leaf dev1 {
      type leafref {
        path "/ncs:devices/ncs:device/ncs:name";
      }
    }
    leaf dev2 {
      type leafref {
        path "/ncs:devices/ncs:device/ncs:name";
      }
    }

    // replace with your own stuff here
    leaf dev1-loop {
      type inet:ipv4-address;
    }
    leaf dev2-loop {
      type inet:ipv4-address;
    }
  }
}
